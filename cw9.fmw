FME workspace cw9.fmw

Parameters:
- SourceDataset_GEOTIFF = ""C:\Users\zuzia\Documents\studia\s5\Bazy danych przestrzennych\cw8\ras250_gb\data\HP.tif" "C:\Users\zuzia\Documents\studia\s5\Bazy danych przestrzennych\cw8\ras250_gb\data\HT.tif" "C:\Users\zuzia\Documents\studia\s5\Bazy danych przestrzennych\cw8\ras250_gb\data\HU.tif" "C:\Users\zuzia\Documents\studia\s5\Bazy danych przestrzennych\cw8\ras250_gb\data\HW.tif" "C:\Users\zuzia\Documents\studia\s5\Bazy danych przestrzennych\cw8\ras250_gb\data\HX.tif" "C:\Users\zuzia\Documents\studia\s5\Bazy danych przestrzennych\cw8\ras250_gb\data\HY.tif" "C:\Users\zuzia\Documents\studia\s5\Bazy danych przestrzennych\cw8\ras250_gb\data\HZ.tif" "C:\Users\zuzia\Documents\studia\s5\Bazy danych przestrzennych\cw8\ras250_gb\data\NA.tif" "C:\Users\zuzia\Documents\studia\s5\Bazy danych przestrzennych\cw8\ras250_gb\data\NB.tif" "C:\Users\zuzia\Documents\studia\s5\Bazy danych przestrzennych\cw8\ras250_gb\data\NC.tif" "C:\Users\zuzia\Documents\studia\s5\Bazy danych przestrzennych\cw8\ras250_gb\data\ND.tif" "C:\Users\zuzia\Documents\studia\s5\Bazy danych przestrzennych\cw8\ras250_gb\data\NF.tif" "C:\Users\zuzia\Documents\studia\s5\Bazy danych przestrzennych\cw8\ras250_gb\data\NG.tif" "C:\Users\zuzia\Documents\studia\s5\Bazy danych przestrzennych\cw8\ras250_gb\data\NH.tif" "C:\Users\zuzia\Documents\studia\s5\Bazy danych przestrzennych\cw8\ras250_gb\data\NJ.tif" "C:\Users\zuzia\Documents\studia\s5\Bazy danych przestrzennych\cw8\ras250_gb\data\NK.tif" "C:\Users\zuzia\Documents\studia\s5\Bazy danych przestrzennych\cw8\ras250_gb\data\NL.tif" "C:\Users\zuzia\Documents\studia\s5\Bazy danych przestrzennych\cw8\ras250_gb\data\NM.tif" "C:\Users\zuzia\Documents\studia\s5\Bazy danych przestrzennych\cw8\ras250_gb\data\NN.tif" "C:\Users\zuzia\Documents\studia\s5\Bazy danych przestrzennych\cw8\ras250_gb\data\NO.tif" "C:\Users\zuzia\Documents\studia\s5\Bazy danych przestrzennych\cw8\ras250_gb\data\NR.tif" "C:\Users\zuzia\Documents\studia\s5\Bazy danych przestrzennych\cw8\ras250_gb\data\NS.tif" "C:\Users\zuzia\Documents\studia\s5\Bazy danych przestrzennych\cw8\ras250_gb\data\NT.tif" "C:\Users\zuzia\Documents\studia\s5\Bazy danych przestrzennych\cw8\ras250_gb\data\NU.tif" "C:\Users\zuzia\Documents\studia\s5\Bazy danych przestrzennych\cw8\ras250_gb\data\NW.tif" "C:\Users\zuzia\Documents\studia\s5\Bazy danych przestrzennych\cw8\ras250_gb\data\NX.tif" "C:\Users\zuzia\Documents\studia\s5\Bazy danych przestrzennych\cw8\ras250_gb\data\NY.tif" "C:\Users\zuzia\Documents\studia\s5\Bazy danych przestrzennych\cw8\ras250_gb\data\NZ.tif" "C:\Users\zuzia\Documents\studia\s5\Bazy danych przestrzennych\cw8\ras250_gb\data\OV.tif" "C:\Users\zuzia\Documents\studia\s5\Bazy danych przestrzennych\cw8\ras250_gb\data\SC.tif" "C:\Users\zuzia\Documents\studia\s5\Bazy danych przestrzennych\cw8\ras250_gb\data\SD.tif" "C:\Users\zuzia\Documents\studia\s5\Bazy danych przestrzennych\cw8\ras250_gb\data\SE.tif" "C:\Users\zuzia\Documents\studia\s5\Bazy danych przestrzennych\cw8\ras250_gb\data\SH.tif" "C:\Users\zuzia\Documents\studia\s5\Bazy danych przestrzennych\cw8\ras250_gb\data\SJ.tif" "C:\Users\zuzia\Documents\studia\s5\Bazy danych przestrzennych\cw8\ras250_gb\data\SK.tif" "C:\Users\zuzia\Documents\studia\s5\Bazy danych przestrzennych\cw8\ras250_gb\data\SM.tif" "C:\Users\zuzia\Documents\studia\s5\Bazy danych przestrzennych\cw8\ras250_gb\data\SN.tif" "C:\Users\zuzia\Documents\studia\s5\Bazy danych przestrzennych\cw8\ras250_gb\data\SO.tif" "C:\Users\zuzia\Documents\studia\s5\Bazy danych przestrzennych\cw8\ras250_gb\data\SP.tif" "C:\Users\zuzia\Documents\studia\s5\Bazy danych przestrzennych\cw8\ras250_gb\data\SR.tif" "C:\Users\zuzia\Documents\studia\s5\Bazy danych przestrzennych\cw8\ras250_gb\data\SS.tif" "C:\Users\zuzia\Documents\studia\s5\Bazy danych przestrzennych\cw8\ras250_gb\data\ST.tif" "C:\Users\zuzia\Documents\studia\s5\Bazy danych przestrzennych\cw8\ras250_gb\data\SU.tif" "C:\Users\zuzia\Documents\studia\s5\Bazy danych przestrzennych\cw8\ras250_gb\data\SV.tif" "C:\Users\zuzia\Documents\studia\s5\Bazy danych przestrzennych\cw8\ras250_gb\data\SW.tif" "C:\Users\zuzia\Documents\studia\s5\Bazy danych przestrzennych\cw8\ras250_gb\data\SX.tif" "C:\Users\zuzia\Documents\studia\s5\Bazy danych przestrzennych\cw8\ras250_gb\data\SY.tif" "C:\Users\zuzia\Documents\studia\s5\Bazy danych przestrzennych\cw8\ras250_gb\data\SZ.tif" "C:\Users\zuzia\Documents\studia\s5\Bazy danych przestrzennych\cw8\ras250_gb\data\TA.tif" "C:\Users\zuzia\Documents\studia\s5\Bazy danych przestrzennych\cw8\ras250_gb\data\TF.tif" "C:\Users\zuzia\Documents\studia\s5\Bazy danych przestrzennych\cw8\ras250_gb\data\TG.tif" "C:\Users\zuzia\Documents\studia\s5\Bazy danych przestrzennych\cw8\ras250_gb\data\TL.tif" "C:\Users\zuzia\Documents\studia\s5\Bazy danych przestrzennych\cw8\ras250_gb\data\TM.tif" "C:\Users\zuzia\Documents\studia\s5\Bazy danych przestrzennych\cw8\ras250_gb\data\TQ.tif" "C:\Users\zuzia\Documents\studia\s5\Bazy danych przestrzennych\cw8\ras250_gb\data\TR.tif" "C:\Users\zuzia\Documents\studia\s5\Bazy danych przestrzennych\cw8\ras250_gb\data\TV.tif""   # Source GeoTIFF File(s) or URL(s)
- SourceDataset_SHAPEFILE = $(FME_MF_DIR)Data\GB\scotland_and_wales_region.shp   # Source Esri Shapefile(s)
- DestDataset_POSTGIS_RASTER = postgis_cw9   # Connection
- DestDataset_GEODATABASE_FILE = $(FME_MF_DIR)results.gdb   # File Geodatabase

Readers:
- GEOTIFF_1: GEOTIFF from $(SourceDataset_GEOTIFF)
- SHAPEFILE_1: SHAPEFILE from $(SourceDataset_SHAPEFILE)

Writers:
- POSTGIS_RASTER_1: POSTGIS_RASTER to $(DestDataset_POSTGIS_RASTER)
- GEODATABASE_FILE_1: GEODATABASE_FILE to $(DestDataset_GEODATABASE_FILE)

scotland_and_wales_region (reader SHAPEFILE_1)
    attributes: NAME varchar(100), AREA_CODE varchar(3), DESCRIPTIO varchar(50), FILE_NAME varchar(100), NUMBER number(11,0), NUMBER0 number(11,0), POLYGON_ID number(11,0), UNIT_ID number(11,0), CODE varchar(9), HECTARES double, AREA double, TYPE_CODE varchar(2), DESCRIPT0 varchar(25), TYPE_COD0 varchar(3), DESCRIPT1 varchar(36)
    -> TestFilter
TestFilter
    DEFAULT_VALUE = <UNFILTERED>
    PASSED_TEST_GROUP_OUTPUT = FIRST
    TEST_LIST = "BOOL_OP,OR,COMPOSITE_TEST,""""""1"""""",TEST_CLAUSE,CASE_INSENSITIVE_TEST @Value(NAME) LIKE South Wales%",South Wales
    South Wales -> Aggregator
Aggregator
    ACCUM_ATTRS = None
    AGGREGATE_TYPE = Homogeneous Collection (If Possible)
    MODE = Geometry - Assemble One Level
    SEP = ,
    AGGREGATE -> SpatialFilter [Filter]
    AGGREGATE -> Clipper [CLIPPER]
GEOTIFF (reader GEOTIFF_1)
    -> Reprojector
    -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> Clipper [CANDIDATE]
Clipper
    ADD_NODATA = YES
    ATTR_ACCUM_MODE = MERGE
    ATTR_CONFLICT_RES = CANDIDATE
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> RasterPaletteRemover
RasterPaletteRemover
    -> exports (writer POSTGIS_RASTER_1)
exports (writer POSTGIS_RASTER_1)
    attributes: _predicate varchar, _clipped char(3)
Reprojector
    DEST = EPSG:4326
    INTERPOLATION_TYPE = NearestNeighbor
    RASTER_CELL_SIZE = PreserveCells
    RASTER_TOLERANCE = 0.0
    REPROJECTED -> RasterExtentsCoercer
RasterExtentsCoercer
    EXTENTS_TYPE_LOOKUP = RasterExtents
    EXTENTS_TYPE = Raster Extents
    EXTENTS -> FilePropertyExtractor_2
FilePropertyExtractor_2
    FMT = FME Date/Time (%Y%m%d%H%M%S)
    PATH = $(FME_MF_DIR_USERTYPED)\$(FME_MF_NAME)
    -> AttributeCreator_2
AttributeCreator_2
    ATTR_TABLE = SET_TO NewName (varchar(200)) = @Value(fme_basename)_@Value(_file_size)
    INPUT_PORT_CONNECTED = CONNECTED
    -> extents (writer GEODATABASE_FILE_1)
extents (writer GEODATABASE_FILE_1)
    attributes: NewName char(200), _file_type char(2048), _file_size char(2048), _file_atime char(2048), _file_mtime char(2048), _file_ctime char(2048)

FME custom transformer FilePropertyExtractor
Extracts basic properties of a file or a directory and adds these attributes to the feature.
    _file_type
    : holds "File" or "Directory", which indicates whether the specified path is a file or a directory.
    _file_size
    : holds the size of file/directory in bytes (total of file sizes if directory)
    _file_atime
    : holds the time of last access.
    _file_mtime
    : holds the time of last modification.
    _file_ctime
    : holds the time of creation on some systems (like Windows), or the time of last metadata change on other systems (like Unix).
    You can specify the format of "_file_atime", "_file_mtime", and "_file_ctime" via the "Date/Time Format" parameter.
    The input feature will be output from the 
    <Rejected>
    port if the specified file/directory does not exist, the path indicates a symbolic link, or an unexpected error has occurred. 
    This transformer contains a Python script, which was tested with both Python 2.7 and Python 3.4 interpreter.
Parameters
    File/Directory Path
    :
    Specify the path of a file or a directory.
    Date/Time Format
    :
    Specify a date/datetime/time format that should be applied to the values of "_file_atime", "_file_mtime", and "_file_ctime". 
    The format syntax is the same as the DateFormatter. See the help doc on the transformer.

Parameters:
- PATH =   # File/Directory Path
- FMT = FME Date/Time (%Y%m%d%H%M%S)

Input (input)
    -> ParameterFetcher
ParameterFetcher
    ATTR_LIST = __filepropertyextractor.path {$(PATH)}
    -> PythonCaller
PythonCaller
    NEW_ATTRIBUTES = _file_type _file_size _file_atime _file_mtime _file_ctime __filepropertyextractor.error
    PYTHONSOURCE:
      # 2016-05-25, Takashi Iijima, Original Implementation
      # 2020-01-28, Takashi Iijima, Calculate Directory Size as Total File Sizes under the Directory; Changed Default Python Interpreter to 3.6+

      import fme, fmeobjects
      import os
      def extractFileProperty(feature):
          def get_dir_size(path):
              total = 0
              for p in os.listdir(path):
                  full_path = os.path.join(path, p)
                  if os.path.isfile(full_path):
                      total += os.path.getsize(full_path)
                  elif os.path.isdir(full_path):
                      total += get_dir_size(full_path)
              return total
          try:
              path = feature.getAttribute('__filepropertyextractor.path')
              if os.path.exists(path) and not os.path.islink(path):
                  s = os.stat(path)
                  if os.path.isdir(path):
                      feature.setAttribute('_file_type', 'Directory')
                      feature.setAttribute('_file_size', get_dir_size(path))
                  else:
                      feature.setAttribute('_file_type', 'File')
                      feature.setAttribute('_file_size', s.st_size)
                  feature.setAttribute('_file_atime', int(s.st_atime))
                  feature.setAttribute('_file_mtime', int(s.st_mtime))
                  feature.setAttribute('_file_ctime', int(s.st_ctime))
              else:
                  raise Exception('specified file/directory does not exist')
          except Exception as ex:
              feature.setAttribute('__filepropertyextractor.error', '%s' % ex)
    PYTHONSYMBOL = extractFileProperty
    -> Tester
Tester
    BOOL_OP = OR
    TEST_CLAUSE = TEST __filepropertyextractor.error ATTRIBUTE_IS_MISSING ""
    TEST_MODE = Automatic
    PASSED -> AttributeRemover
    FAILED -> AttributeRemover_2
AttributeRemover
    REMOVE_ATTRS = __filepropertyextractor.path,__filepropertyextractor.error
    -> DateFormatter
DateFormatter
    DATE_ATTR = _file_ctime,_file_mtime,_file_atime
    FMT = $(FMT)
    INVALID_DATE_VALUE = _FME_NO_OP_
    SRCFMT_LU = %s
    SRCFMT = %s
    -> Output (output)
Output (output)
AttributeRemover_2
    REMOVE_ATTRS = _file_size,_file_type,_file_ctime,__filepropertyextractor.path,_file_mtime,_file_atime
    -> AttributeRenamer
AttributeRenamer
    ATTR_TABLE = RENAME_SET_DEFAULT __filepropertyextractor.error > _rejected_reason
    -> <Rejected> (output)
<Rejected> (output)
